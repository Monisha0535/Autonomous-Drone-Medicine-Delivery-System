# Autonomous_Cleaning_System

## REQ - 0: The user shall program the time in which the system turns on. (Functional)

### REQ - 0.2: The cleaning robot shall emit the turning on signal. (Functional)

### REQ - 0.1: The timer shall be set. (Informational)

## REQ - 1: The cleaning robot shall clean autonomously the house floors. (Functional)

### REQ - 1.1: The cleaning robot shall remove the dust. (Informational)

## REQ - 2: The cleaning system shall use the sensors to navigate within the environment. (Functional)

### REQ - 2.1: The cleaning robot shall detect obstacles. (Functional)

### REQ - 2.2: If an obstacle is detected, the cleaning robot shall avoid the obstacle. (Functional)

#### REQ - 2.2.1: The cleaning robot shall change the direction when the obstacle is within 20cm. (Informational)

## REQ - 3: The cleaning robot shall detect the different types of floors. (Functional)

### REQ - 3.1: The cleaning robot shall adjust the the action according to the type of floor. (Functional)

#### REQ - 3.1.1: If a marble floor is detected, the cleaning system shall enable gentle surface function. (Informational)

#### REQ - 3.1.2: If a wood floor is detected, the cleaning system shall enable wood surface function. (Informational)

#### REQ - 3.1.3: If a carpet is detected, the cleaning system shall enable carpet surface function. (Informational)

## REQ - 4: When the cleaning robot has finished to clean the house, the cleaning robot shall return to the docking station. (Functional)

### REQ - 4.1: The docking station shall charge the cleaning robot. (Functional)

### REQ - 4.2: The docking station shall turn off the cleaning robot. (Functional)

### REQ - 4.3: The cleaning robot shall emit the turning off signal. (Functional)
