# Cruisecntrlsys

## #1: The system shall control the vehicle's speed (Functional)

### #12: The system shall maintain the speed within 10% error compared to reference speed. (Functional)

## #4: When the system is set on, the speed manager shall set the current speed as a reference. (Functional)

## #5: when the system is set off, the speed manager shall delete all the speed data. (Functional)

## #6: The speed manager shall set the system on. (Functional)

## #7: The speed manager shall set the system off (Functional)

## #8: The speed manager shall pause the system. (Functional)

## #9: The speed manager shall run the system. (Functional)

## #10: When the system switches on pause state, the system shall record the reference speed. (Functional)

## #11: When the system switches to "run" state, the system shall set the recorded speed as reference. (Functional)
